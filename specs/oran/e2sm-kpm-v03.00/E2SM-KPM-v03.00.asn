-- ==============================================================================
-- O-RAN Service Model for Key Performance Measurements (E2SM-KPM) v03.00
-- Referência: O-RAN.WG3.E2SM-KPM-v03.00 / O-RAN SC Release I/J
-- ==============================================================================

E2SM-KPM-v03.00 DEFINITIONS AUTOMATIC TAGS ::= BEGIN

E2SM-KPM-EventTriggerDefinition ::= SEQUENCE {
    eventDefinition-formats CHOICE {
        eventDefinition-Format1 E2SM-KPM-EventTriggerDefinition-Format1,
        ...
    },
    ...
}

E2SM-KPM-EventTriggerDefinition-Format1 ::= SEQUENCE {
    reportingPeriodMs   INTEGER (1..3600000),
    ...
}

E2SM-KPM-ActionDefinition ::= SEQUENCE {
    ric-Style-Type              RIC-Style-Type,
    actionDefinition-formats    CHOICE {
        actionDefinition-Format1 E2SM-KPM-ActionDefinition-Format1,
        ...
    },
    ...
}

E2SM-KPM-ActionDefinition-Format1 ::= SEQUENCE {
    measInfoList    MeasurementInfoList,
    granulPeriod    GranularityPeriod,
    ...
}

MeasurementInfoList ::= SEQUENCE (SIZE(1..65535)) OF MeasurementInfoItem

MeasurementInfoItem ::= SEQUENCE {
    measType    MeasurementType,
    measID      MeasurementTypeID OPTIONAL,
    ...
}

MeasurementType ::= CHOICE {
    measName    PrintableString(SIZE(1..150,...)),
    measID      MeasurementTypeID,
    ...
}

MeasurementTypeID ::= INTEGER (1..65536, ...)
RIC-Style-Type ::= INTEGER (1..255, ...)
GranularityPeriod ::= INTEGER (1..3600000)

E2SM-KPM-IndicationMessage ::= SEQUENCE {
    indicationMessage-formats CHOICE {
        indicationMessage-Format1 E2SM-KPM-IndicationMessage-Format1,
        ...
    },
    ...
}

E2SM-KPM-IndicationMessage-Format1 ::= SEQUENCE {
    measData    MeasurementData,
    measInfoList MeasurementInfoList OPTIONAL,
    granulPeriod GranularityPeriod OPTIONAL,
    ...
}

MeasurementData ::= SEQUENCE (SIZE(1..65535)) OF MeasurementDataItem

MeasurementDataItem ::= SEQUENCE {
    measRecord  MeasurementRecord,
    ...
}

MeasurementRecord ::= SEQUENCE (SIZE(1..65535)) OF MeasurementRecordItem

MeasurementRecordItem ::= CHOICE {
    integer     INTEGER (0..4294967295),
    real        REAL,
    noValue     NULL,
    ...
}

END
